-- **********************************************************
-- Copyright 2007 VMware, Inc.  All rights reserved. 
-- **********************************************************

VMWARE-TC-MIB DEFINITIONS ::= BEGIN

    IMPORTS
        MODULE-IDENTITY
    FROM SNMPv2-SMI
        TEXTUAL-CONVENTION
    FROM SNMPv2-TC
        vmwSystem
    FROM VMWARE-ROOT-MIB;

    vmwTcMIB MODULE-IDENTITY
    LAST-UPDATED "200903170000Z"
    ORGANIZATION "VMware, Inc"
    CONTACT-INFO
    "VMware, Inc
    3401 Hillview Ave
    Palo Alto, CA 94304
    Tel: 1-877-486-9273 or 650-427-5000
    Fax: 650-427-5001
    "
DESCRIPTION
    "This MIB module provides common datatypes for use in VMWARE 
     enterprise mib modules"
REVISION      "200903170000Z"
DESCRIPTION
    "Added VmwLongDisplayString"
REVISION      "200712270000Z"
DESCRIPTION
    "This is the first revision."
::= { vmwSystem 11 }

VmwSubsystemTypes ::= TEXTUAL-CONVENTION
    STATUS       current
    DESCRIPTION
            "Define the various subsystems fond on hardware."
    SYNTAX   INTEGER { unknown(1), chassis(2), powerSupply(3), fan(4), cpu(5), 
                       memory(6), battery(7), temperatureSensor(8), 
                       raidController(9), voltage(10) 
                     }

VmwSubsystemStatus ::= TEXTUAL-CONVENTION
    STATUS       current
    DESCRIPTION
            "Define the state oof a given subsystem if known."
    SYNTAX  INTEGER { unknown(1), normal(2), marginal(3), critical(4), failed(5) }

VmwConnectedState ::= TEXTUAL-CONVENTION
    DISPLAY-HINT "7a" 
    STATUS       current
    DESCRIPTION
            "Can hold one of the following values: 'true' or 'false' or 'unknown'."
    SYNTAX  OCTET STRING (SIZE (7))

VmwLongDisplayString ::= TEXTUAL-CONVENTION
    DISPLAY-HINT "1a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            An object defined using this syntax may be of indefinite
            length, as specified by the protocol, but displays may
            choose to display only the first 4096 characters."
    SYNTAX       OCTET STRING 

END
