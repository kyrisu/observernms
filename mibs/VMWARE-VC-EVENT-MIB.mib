-- **********************************************************
-- Copyright 2008 VMware, Inc.  All rights reserved. 
-- **********************************************************

VMWARE-VC-EVENT-MIB DEFINITIONS ::= BEGIN

    IMPORTS
        MODULE-IDENTITY, OBJECT-TYPE, NOTIFICATION-TYPE
        FROM SNMPv2-SMI
        DisplayString
        FROM SNMPv2-TC
        MODULE-COMPLIANCE, OBJECT-GROUP, NOTIFICATION-GROUP
        FROM SNMPv2-CONF
        -- add these for HP SIM
        --vmwProductSpecific
        --FROM VMWARE-ROOT-MIB;
        -- remove these for HP SIM
        vmwVC 
        FROM VMWARE-PRODUCTS-MIB
        VmwLongDisplayString
        FROM VMWARE-TC-MIB;

    vmwVCMIB MODULE-IDENTITY
    LAST-UPDATED "200904060000Z"
    ORGANIZATION "VMware, Inc"
    CONTACT-INFO
    "VMware, Inc
    3401 Hillview Ave
    Palo Alto, CA 94304
    Tel: 1-877-486-9273 or 650-427-5000
    Fax: 650-427-5001
    "
DESCRIPTION
     "This MIB module identifies VirtualCenter Trap notifications (traps or inform)."
REVISION      "200904060000Z"
DESCRIPTION
    "Swap vmwVpxdNewStatus and vmwVpxdOldStatus to match code implementation."
REVISION      "200903170000Z"
DESCRIPTION
    "Changed vmwVpxdObjValue be of type vmwLongDisplayString"
REVISION      "200802220000Z"
DESCRIPTION
    "This is the first revision in SMIv2 format. Prior version was published as SMIv1.
     Notifications were formerly in the VMWARE-TRAPS-MIB module."
::= { vmwVC 1 }


-- product compatiblity: smilint warning: redefinition of vmwVC in VMWARE-PRODUCTS-MIB
-- The folowing redefinition of vmwVC is a workaround for HP SIM which
-- doesn't process IMPORTS more than one level deep.
-- vmwVC OBJECT IDENTIFIER ::= { vmwProductSpecific 3 }

vmwVCNotifications OBJECT IDENTIFIER ::= {vmwVC 0 }

-- **********************************************************
-- Notifications by an agent that implements this mib module
-- **********************************************************

vpxdAlarm NOTIFICATION-TYPE
    OBJECTS { vmwVpxdTrapType, vmwVpxdHostName, vmwVpxdVMName, 
	      vmwVpxdOldStatus, vmwVpxdNewStatus, vmwVpxdObjValue }
    STATUS      current 
    DESCRIPTION 
        "This trap is sent when entity alarm status changed."
    ::= { vmwVCNotifications 201 }
	
vpxdDiagnostic NOTIFICATION-TYPE
    STATUS      current
    DESCRIPTION
        "This trap is sent on starting or restarting VirtualCenter Server, 
         on requesting a test notification explicitly, and can also be 
         configured to be sent periodically at a specified time interval via 
         VirtualCenter Server configuration."
    ::= { vmwVCNotifications 202 }


-- **********************************************************
-- Notification parameters
-- **********************************************************

vmwVpxdTrapType OBJECT-TYPE
    SYNTAX     DisplayString 
    MAX-ACCESS accessible-for-notify
    STATUS     current
    DESCRIPTION
	"This is the trap type in the preceding traps."
    ::= { vmwVC 301 }

vmwVpxdHostName OBJECT-TYPE
    SYNTAX     DisplayString 
    MAX-ACCESS accessible-for-notify
    STATUS     current
    DESCRIPTION
	"This is the name of the host in the preceding traps."
    ::= { vmwVC 302 }

vmwVpxdVMName OBJECT-TYPE
    SYNTAX     DisplayString
    MAX-ACCESS accessible-for-notify
    STATUS     current
    DESCRIPTION
        "This is the name of the VM in the preceding traps."
    ::= { vmwVC 303 }

vmwVpxdOldStatus OBJECT-TYPE
    SYNTAX     DisplayString 
    MAX-ACCESS accessible-for-notify
    STATUS     current
    DESCRIPTION
	"This is the old status in the preceding traps."
    ::= { vmwVC 304 }

vmwVpxdNewStatus OBJECT-TYPE
    SYNTAX     DisplayString 
    MAX-ACCESS accessible-for-notify
    STATUS     current
    DESCRIPTION
	"This is the new status in the preceding traps."
    ::= { vmwVC 305 }

vmwVpxdObjValue OBJECT-TYPE
    SYNTAX     VmwLongDisplayString
    MAX-ACCESS accessible-for-notify
    STATUS     current
    DESCRIPTION
	"This is the current object value in the preceding traps."
    ::= { vmwVC 306 }

-- conformance information
vmwVCMIBConformance OBJECT IDENTIFIER ::= { vmwVCMIB 2 }
vmwVCMIBCompliances OBJECT IDENTIFIER ::= { vmwVCMIBConformance 1 }
vmwVCMIBGroups OBJECT IDENTIFIER ::= { vmwVCMIBConformance 2 }

-- compliance statements
vmwVCMIBBasicCompliance MODULE-COMPLIANCE
    STATUS     current
    DESCRIPTION
        "The compliance statement for entities which implement VMWARE-VC-EVENT-MIB."
    MODULE -- this module 
    MANDATORY-GROUPS { vmwVCAlarmInfoGroup, vmwVCNotificationGroup }
    ::= { vmwVCMIBCompliances 2 }

vmwVCAlarmInfoGroup OBJECT-GROUP
    OBJECTS {
    vmwVpxdTrapType,
    vmwVpxdHostName,
    vmwVpxdVMName, 
    vmwVpxdOldStatus,
    vmwVpxdNewStatus,
    vmwVpxdObjValue 
    }
    STATUS current
    DESCRIPTION 
	"These objects provide alarm trap details"
    ::= { vmwVCMIBGroups 1 }

vmwVCNotificationGroup NOTIFICATION-GROUP
       NOTIFICATIONS {
          vpxdAlarm,
          vpxdDiagnostic
       }
       STATUS current
       DESCRIPTION 
           "Group of objects describing notifications (traps)."
       ::= { vmwVCMIBGroups 2 }  
 
END -- end of VMWARE-VC-EVENT-MIB.
